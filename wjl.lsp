;;几字钢屋架梁长度计算，屋面角23°
;;屋脊连接件孔中心距l1=63.53mm l2=118.7mm
;;以雨槽支撑件底板中点为原点，侧耳靠下孔中心为(120.8  118.1)
;;设两雨槽支撑件中点距离为d


(defun wjl (d)
  ;;根据雨槽支撑件中心距d，计算屋架梁长度及孔中心距离
  (setq l1 63.53
	; l2 117
	dx 120.8
	; dy 247.51
	a  0.4014);23°的弧度

  ;|(setq l (- (/ (/ (- d (* 2 dx)) 2)
		(cos a))
	     (/ (/ l1 2) (cos a))
	     )
	rzl-l (+ l 20 48)
	)|;
  (setq ll (/ (/ (- (- d (* 2 dx))
                 l1)
                2)
              (cos a))
        rzl-l (+ ll 20 50)
        )
              
  (princ (strcat "几字钢屋架梁长边长" (rtos rzl-l 2) ", 夹角60.5度,"))
  (princ (strcat "最远两孔距" (rtos ll 2)))
  (princ "\n最上孔向上20为边，向下30为一孔心\73 最下孔向上40为一孔心")
  (princ)
  )

  
 

(wjl (getreal "请输入小屋脊跨度："))
